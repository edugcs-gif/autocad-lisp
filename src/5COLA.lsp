(vl-load-com)

(defun strip (s)
  (vl-string-trim " \t\r\n" s)
)

(defun read-dxf-pairs (path / f code val pairs)
  (setq f (open path "r"))
  (setq pairs '())
  (while (and f (setq code (read-line f)))
    (setq val (read-line f))
    (setq pairs (cons (cons (atoi (strip code)) val) pairs))
  )
  (if f (close f))
  (reverse pairs)
)

(defun make-polyline (verts / vlist)
  (if (>= (length verts) 2)
    (progn
      (setq vlist (list (cons 0 "LWPOLYLINE")
                         (cons 100 "AcDbEntity")
                         (cons 8 "0")
                         (cons 100 "AcDbPolyline")
                         (cons 90 (length verts))
                         (cons 70 1)
                         (cons 43 0.0)
                   )
      )
      (foreach v verts
        (setq vlist (append vlist (list (cons 10 v))))
      )
      (entmake vlist)
    )
  )
)

(defun c:5COLA (/ dxfpath pairs n i p val cur-code verts xval count)
  (setq dxfpath (strcat (getenv "USERPROFILE") "\\Desktop\\dxf\\Exportado(DXF).dxf"))
  (if (not (findfile dxfpath))
    (princ "\nArquivo Exportado(DXF).dxf não encontrado.")
    (progn
      (setq pairs (read-dxf-pairs dxfpath))
      (setq n (length pairs))
      (setq i 0)
      (setq count 0)
      (while (< i n)
        (setq p (nth i pairs))
        (if (and (= (car p) 0) (= (strip (cdr p)) "LWPOLYLINE"))
          (progn
            (setq verts '())
            (setq xval nil)
            (setq i (1+ i))
            (while (and (< i n) (/= (car (nth i pairs)) 0))
              (setq p (nth i pairs))
              (setq cur-code (car p))
              (setq val (cdr p))
              (cond
                ((= cur-code 10) (setq xval (atof val)))
                ((= cur-code 20) (setq verts (cons (list xval (atof val)) verts)))
              )
              (setq i (1+ i))
            )
            (setq verts (reverse verts))
            (make-polyline verts)
            (setq count (1+ count))
          )
          (setq i (1+ i))
        )
      )
      (princ (strcat "\n" (itoa count) " polígono(s) colado(s) na coordenada original."))
    )
  )
  (princ)
)
